FME workspace kpi-processor_V2.fmw

Parameters:
- TEXT = perp_year_nbr between 2009 and 2010   # MSSQL_ADO_IN_WHERE_CLAUSE_MSSQL_ADO Which year to process

Readers:
- MSSQL_ADO_1: MSSQL_ADO from SQLDEV

Writers:
- MSSQL_ADO_2: MSSQL_ADO to SQLDEV

Junction_4
    -> Sorter_3
Junction_2
    -> Sorter_2
Junction_34
    -> Sorter_2
Junction_24
    -> Sorter_3
Junction_36
    -> Sorter_2
Junction_26
    -> Sorter_3
Junction_32
    -> Sorter_2
Junction_22
    -> Sorter_3
Junction_38
    -> Sorter_2
Junction_28
    -> Sorter_3
Junction_40
    -> Sorter_2
Junction_30
    -> Sorter_3
Junction_44
    -> Sorter_2
Junction_46
    -> Sorter_3
Junction_6
    -> Sorter_2
Junction_8
    -> Sorter_3
Sorter_5_SORTED_-__Tester_7: Junction
    -> DuplicateFilter
DuplicateFilter
    KEYATTR = RIGHT_RUTTING_NBR FIPS_CD CTL_END_NBR LANES_NBR LIRI_NBR CRACKING_PCT_NBR_PCR DOWN_RI_PVMT_TYPE_CD DIRECTION_CD REENTER_IND TRUCK_AADT_NBR AADT_NBR CRACKING_PCT_NBR MPO_NAME MUNICIPALITY_NME PERP_YEAR_NBR PCR_NBR RIDE_NBR RIGHT_FAULTING_NBR AVG_FAULTING_NBR_PCR LEFT_RUTTING_NBR COUNTY_ABREV3_CD IRI_PROVIDER CAR_AADT_NBR NLF_ID FAULTING_SAMPLE_IND LEAVE_IND NHS_CD RIRI_NBR RUTTING_SAMPLE_IND AVG_RUTTING_NBR_PCR CRACKING_SAMPLE_IND PCR_YEAR_NBR AVG_FAULTING_NBR PVMT_TYPE_CD CTL_BEGIN_NBR MPO_CD LEFT_FAULTING_NBR AVG_RUTTING_NBR PSR_PCR_NBR HCS_NBR DIVIDED_HWY_IND CRACKING_LENGTH_NBR UP_RI_PVMT_TYPE_CD PRIORITY_SYSTEM_CD
    INPUT_ORDERED_CHOICE = No
    UNIQUE -> Tester_7
AttributeRenamer
    ATTR_TABLE = RENAME_SET_DEFAULT PVMT_TYPE_CD > PCR_PVMT_TYPE_CD
    -> AttributeRounder
AttributeRounder
    ROUND_TYPE = Nearest
    SRC_ATTRS = CTL_END_NBR CTL_BEGIN_NBR SEGMENT_LENGTH_NBR
    PLACES = 3
    -> PERF_SEGMENTS_HISTORY (writer MSSQL_ADO_2)
PERF_SEGMENTS_HISTORY (writer MSSQL_ADO_2)
    attributes: PERF_SEGMENTS_HISTORY_ID identity, PCR_YEAR_NBR integer, PERP_YEAR_NBR integer, COUNTY_ABREV3_CD char(3), NLF_ID char(14), DIRECTION_CD varchar(4), CTL_BEGIN_NBR numeric(7,3), CTL_END_NBR numeric(7,3), LEAVE_IND char(1), REENTER_IND char(1), SEGMENT_LENGTH_NBR numeric(7,3), PRIORITY_SYSTEM_CD char(1), NHS_CD char(1), LANES_NBR integer, FIPS_CD char(5), MUNICIPALITY_NME varchar(18), MPO_CD varchar(12), MPO_NAME varchar(25), DIVIDED_HWY_IND char(1), UP_RI_PVMT_TYPE_CD varchar(10), DOWN_RI_PVMT_TYPE_CD varchar(10), LEFT_FAULTING_NBR numeric(4,2), RIGHT_FAULTING_NBR numeric(4,2), AVG_FAULTING_NBR numeric(4,2), LEFT_RUTTING_NBR numeric(4,2), RIGHT_RUTTING_NBR numeric(4,2), AVG_RUTTING_NBR numeric(4,2), CRACKING_PCT_NBR numeric(5,2), CRACKING_LENGTH_NBR integer, AADT_NBR integer,
      CAR_AADT_NBR integer, TRUCK_AADT_NBR integer, PCR_NBR numeric(4,0), PCR_PVMT_TYPE_CD varchar(10), LIRI_NBR numeric(10,0), RIRI_NBR numeric(10,0), AVG_IRI_NBR numeric(10,0), HCS_NBR numeric(10,0), RIDE_NBR numeric(4,2), PSR_NBR numeric(4,2), FAULTING_PROVIDER varchar(25), CRACKING_PROVIDER varchar(25), PSR_PROVIDER varchar(25), RUTTING_PROVIDER varchar(25), IRI_PROVIDER varchar(25), SPEED_LIMIT_NBR integer

Bookmark: LRS segments
dbo.LRS_SEGMENTS (reader MSSQL_ADO_1)
    attributes: LRS_SEGMENTS_ID identity, PERP_YEAR_NBR integer, COUNTY_ABREV3_CD char(3), NLF_ID char(14), CTL_BEGIN_NBR numeric(7,3), CTL_END_NBR numeric(7,3), CTL_3D_BEGIN_NBR numeric(7,3), CTL_3D_END_NBR numeric(7,3), LEAVE_IND char(1), REENTER_IND char(1), SEGMENT_LENGTH_NBR numeric(7,3), SEGMENT_LENGTH_3D_NBR numeric(7,3), PRIORITY_SYSTEM_CD char(1), NHS_CD char(1), LANE_WIDTH_NBR numeric(9,5), LANES_NBR integer, FIPS_CD char(5), MUNICIPALITY_NME varchar(18), DIVIDED_HWY_IND char(1), UP_RI_PVMT_TYPE_CD varchar(10), DOWN_RI_PVMT_TYPE_CD varchar(10), MPO_CD varchar(12), MPO_NAME varchar(25), SPEED_LIMIT_NBR integer
    -> Junction_41
    -> Junction_9
    -> Junction_19
    -> Junction_11
    -> Junction_13
    -> Junction_15
    -> Junction_17
    -> AttributeRounder_2
Junction_41
    -> Junction_42
AttributeRounder_2
    ROUND_TYPE = Nearest
    SRC_ATTRS = CTL_END_NBR CTL_BEGIN_NBR
    PLACES = 3
    -> AttributeKeeper_4
AttributeKeeper_4
    KEEP_ATTRS = REENTER_IND,NLF_ID,UP_RI_PVMT_TYPE_CD,CTL_BEGIN_NBR,DIVIDED_HWY_IND,FIPS_CD,LEAVE_IND,NHS_CD,CTL_END_NBR,SPEED_LIMIT_NBR,MUNICIPALITY_NME,PERP_YEAR_NBR,DOWN_RI_PVMT_TYPE_CD,PRIORITY_SYSTEM_CD,COUNTY_ABREV3_CD,LANES_NBR
    -> Junction_3
    -> Junction
Note: Sorter_3 : Input
Junction_3
    -> Junction_4
Note: Sorter_2 : Input
Junction
    -> Junction_2
Junction_9
    -> Junction_10
Junction_19
    -> Junction_20
Junction_11
    -> Junction_12
Junction_13
    -> Junction_14
Junction_15
    -> Junction_16
Junction_17
    -> Junction_18

Bookmark: Without direction
Note: dbo.LRS_SEGMENTS
Junction_42
    -> FeatureMerger_7 [SUPPLIER]
Junction_10
    -> FeatureMerger [SUPPLIER]
dbo.MPO_SEGMENT_HISTORY (reader MSSQL_ADO_1)
    attributes: MPO_SEGMENT_ID identity, PERP_YEAR_NBR integer, NLF_ID char(14), CTL_BEGIN_NBR numeric(7,3), CTL_END_NBR numeric(7,3), SEGMENT_LENGTH_NBR numeric(7,3), MPO_CD varchar(12), MPO_NAME varchar(25)
    -> FeatureMerger_7 [REQUESTOR]
FeatureMerger_7
    PROCESS_DUPS = Yes
    REJECT_NULL_MISSING_KEYS = No
    CONNECT_Z_MODE = First Wins
    IGNORE_NULLS = No
    MERGE_TYPE = Attributes Only
    ATTR_CONFLICT_RES = Use Requestor
    GEOM_TYPE = Build Polygons
    JOIN_KEYS = @Value(NLF_ID) @Value(NLF_ID) AUTO
    ATTR_ACCUM_MODE = Merge Supplier
    SUPPLIERS_FIRST = No
    MERGED -> AttributeKeeper_8
AttributeKeeper_8
    KEEP_ATTRS = MPO_CD,NLF_ID,CTL_BEGIN_NBR,CTL_END_NBR,MPO_NAME,PERP_YEAR_NBR
    -> AttributeRounder_9
AttributeRounder_9
    ROUND_TYPE = Nearest
    SRC_ATTRS = CTL_END_NBR CTL_BEGIN_NBR
    PLACES = 3
    -> Junction_43
    -> Junction_45
Note: Sorter_2 : Input
Junction_43
    -> Junction_44
Note: Sorter_3 : Input
Junction_45
    -> Junction_46
dbo.HPMS_AADT_HISTORY (reader MSSQL_ADO_1)
    attributes: HPMS_AADT_HISTORY_ID integer, PERP_YEAR_NBR integer, NLF_ID char(14), CTL_BEGIN_NBR numeric(7,3), CTL_END_NBR numeric(7,3), SEGMENT_LENGTH_NBR numeric(7,3), AADT_NBR integer, CAR_AADT_NBR integer, TRUCK_AADT_NBR integer
    -> FeatureMerger [REQUESTOR]
FeatureMerger
    PROCESS_DUPS = Yes
    REJECT_NULL_MISSING_KEYS = No
    CONNECT_Z_MODE = First Wins
    IGNORE_NULLS = No
    MERGE_TYPE = Attributes Only
    ATTR_CONFLICT_RES = Use Requestor
    GEOM_TYPE = Build Polygons
    JOIN_KEYS = @Value(NLF_ID) @Value(NLF_ID) AUTO
    ATTR_ACCUM_MODE = Merge Supplier
    SUPPLIERS_FIRST = No
    MERGED -> AttributeKeeper_5
AttributeKeeper_5
    KEEP_ATTRS = CTL_END_NBR,NLF_ID,AADT_NBR,TRUCK_AADT_NBR,CAR_AADT_NBR,CTL_BEGIN_NBR,PERP_YEAR_NBR
    -> AttributeRounder_7
AttributeRounder_7
    ROUND_TYPE = Nearest
    SRC_ATTRS = CTL_END_NBR CTL_BEGIN_NBR
    PLACES = 3
    -> Junction_5
    -> Junction_7
Note: Sorter_2 : Input
Junction_5
    -> Junction_6
Note: Sorter_3 : Input
Junction_7
    -> Junction_8

Bookmark: With direction
Junction_20
    -> FeatureMerger_2 [SUPPLIER]
Junction_12
    -> FeatureMerger_3 [SUPPLIER]
Junction_14
    -> FeatureMerger_4 [SUPPLIER]
Junction_16
    -> FeatureMerger_6 [SUPPLIER]
Junction_18
    -> FeatureMerger_5 [SUPPLIER]
dbo.PMS_ROUGHNESS_HISTORY (reader MSSQL_ADO_1)
    attributes: ROUGHNESS_HISTORY_ID char(32), VERSION_ID integer, HISTORY_ROUTE_ID char(32), PCR_YEAR_NBR integer, PERP_YEAR_NBR integer, COUNTY_ABREV3_CD char(3), NLF_ID char(14), ROUTE_TXT char(5), ROUTE_SUFFIX_CD char(1), DIRECTION_CD varchar(4), SLM_BEGIN_NBR numeric(7,3), BACKSTATION_BEGIN_CD char(1), SLM_END_NBR numeric(7,3), BACKSTATION_END_CD char(1), CTL_BEGIN_NBR numeric(7,3), CTL_END_NBR numeric(7,3), LEAVE_IND char(1), REENTER_IND char(1), GAP_LEAVE_IND char(1), GAP_REENTER_IND char(1), SEGMENT_LENGTH_NBR numeric(7,3), SAMPLE_LENGTH_NBR numeric(7,3), RATED_DT varchar(25), EQUIPMENT_TXT varchar(2), TEAM_TXT varchar(4), LIRI_NBR numeric(10,0), RIRI_NBR numeric(10,0), HCS_NBR numeric(10,0), RIDE_NBR numeric(4,2), PAUSE_IND char(1)
    -> FeatureMerger_3 [REQUESTOR]
FeatureMerger_3
    PROCESS_DUPS = Yes
    REJECT_NULL_MISSING_KEYS = No
    CONNECT_Z_MODE = First Wins
    IGNORE_NULLS = No
    MERGE_TYPE = Attributes Only
    ATTR_CONFLICT_RES = Use Requestor
    GEOM_TYPE = Build Polygons
    JOIN_KEYS = @Value(NLF_ID) @Value(NLF_ID) AUTO
    ATTR_ACCUM_MODE = Merge Supplier
    SUPPLIERS_FIRST = No
    MERGED -> AttributeKeeper_7
AttributeKeeper_7
    KEEP_ATTRS = CTL_END_NBR,HCS_NBR,NLF_ID,LIRI_NBR,RIDE_NBR,DIRECTION_CD,CTL_BEGIN_NBR,PCR_YEAR_NBR,PERP_YEAR_NBR,RIRI_NBR
    -> AttributeRounder_5
AttributeRounder_5
    ROUND_TYPE = Nearest
    SRC_ATTRS = CTL_END_NBR CTL_BEGIN_NBR
    PLACES = 3
    -> AttributeCreator_2
AttributeCreator_2
    ATTR_TABLE = SET_TO IRI_PROVIDER = ROUGHNESS
    -> Direction_2
Direction_2: Tester
    TEST_DESCRIPTION = ""
    TEST_CLAUSE = TEST @Value(DIRECTION_CD) = UP
    TEST_MODE = Automatic
    BOOL_OP = OR
    PASSED -> Junction_33
    FAILED -> Junction_23
Note: Sorter_2 : Input
Junction_33
    -> Junction_34
Note: AttributeRenamer_5 : Input
Junction_23
    -> Junction_24
dbo.FAULTING_HISTORY (reader MSSQL_ADO_1)
    attributes: FAULTING_HISTORY_ID identity, PERP_YEAR_NBR integer, PCR_YEAR_NBR integer, NLF_ID char(14), CTL_BEGIN_NBR numeric(7,3), CTL_END_NBR numeric(7,3), SEGMENT_LENGTH_NBR numeric(7,3), COLLECTION_DT varchar(20), DIRECTION_CD varchar(4), LEFT_FAULTING_NBR numeric(4,2), RIGHT_FAULTING_NBR numeric(4,2), AVG_FAULTING_NBR numeric(4,2), LATITUDE_BEGIN_NBR numeric(10,8), LONGITUDE_BEGIN_NBR numeric(10,8), LATITUDE_END_NBR numeric(10,8), LONGITUDE_END_NBR numeric(10,8), DATA_PROVIDER_TXT varchar(32)
    -> FeatureMerger_4 [REQUESTOR]
FeatureMerger_4
    PROCESS_DUPS = Yes
    REJECT_NULL_MISSING_KEYS = No
    CONNECT_Z_MODE = First Wins
    IGNORE_NULLS = No
    MERGE_TYPE = Attributes Only
    ATTR_CONFLICT_RES = Use Requestor
    GEOM_TYPE = Build Polygons
    JOIN_KEYS = @Value(NLF_ID) @Value(NLF_ID) AUTO
    ATTR_ACCUM_MODE = Merge Supplier
    SUPPLIERS_FIRST = No
    MERGED -> AttributeKeeper_3
AttributeKeeper_3
    KEEP_ATTRS = CTL_END_NBR,NLF_ID,DIRECTION_CD,RIGHT_FAULTING_NBR,CTL_BEGIN_NBR,PCR_YEAR_NBR,PERP_YEAR_NBR,AVG_FAULTING_NBR,LEFT_FAULTING_NBR
    -> AttributeRounder_3
AttributeRounder_3
    ROUND_TYPE = Nearest
    SRC_ATTRS = CTL_END_NBR CTL_BEGIN_NBR
    PLACES = 3
    -> Direction_3
Direction_3: Tester
    TEST_DESCRIPTION = ""
    TEST_CLAUSE = TEST @Value(DIRECTION_CD) = UP
    TEST_MODE = Automatic
    BOOL_OP = OR
    PASSED -> Junction_35
    FAILED -> Junction_25
Note: Sorter_2 : Input
Junction_35
    -> Junction_36
Note: AttributeKeeper_10 : Input
Junction_25
    -> Junction_26
dbo.PCR_HISTORY_CONDITION (reader MSSQL_ADO_1)
    attributes: PCR_HISTORY_CONDITION_ID bigint, PCR_HISTORY_ID char(32), DIVIDED_HWY_IND char(1), PVMT_TYPE_CD varchar(10), CTL_BEGIN_NBR numeric(7,3), LEAVE_IND char(1), DIRECTION_CD varchar(4), FORM_NBR integer, CTL_END_NBR numeric(7,3), PERP_YEAR_NBR integer, NLF_ID char(14), PCR_NBR numeric(4,0), REENTER_IND char(1), SEGMENT_LENGTH_NBR numeric(7,3), PCR_YEAR_NBR integer, COUNTY_ABREV3_CD char(3), GAP_REENTER_IND char(1), GAP_LEAVE_IND char(1), FAULT_SEVERITY_CD char(1), FAULT_EXTENT_CD char(1), RUT_SEVERITY_CD char(1), RUT_EXTENT_CD char(1), LONG_SEVERITY_CD varchar(1), LONG_EXTENT_CD varchar(1), TCSR_SEVERITY_CD varchar(1), TCSR_EXTENT_CD varchar(1), TCSP_SEVERITY_CD varchar(1), TCSP_EXTENT_CD varchar(1), WHEEL_SEVERITY_CD varchar(1), WHEEL_EXTENT_CD varchar(1),
      FAULTING_SAMPLE_IND varchar(1), AVG_FAULTING_NBR numeric(4,2), RUTTING_SAMPLE_IND char(1), AVG_RUTTING_NBR numeric(4,2), CRACKING_PCT_NBR numeric(5,2), CRACKING_SAMPLE_IND varchar(1), PSR_PCR_NBR numeric(4,2)
    -> FeatureMerger_2 [REQUESTOR]
FeatureMerger_2
    PROCESS_DUPS = Yes
    REJECT_NULL_MISSING_KEYS = No
    CONNECT_Z_MODE = First Wins
    IGNORE_NULLS = No
    MERGE_TYPE = Attributes Only
    ATTR_CONFLICT_RES = Use Requestor
    GEOM_TYPE = Build Polygons
    JOIN_KEYS = @Value(NLF_ID) @Value(NLF_ID) AUTO
    ATTR_ACCUM_MODE = Merge Supplier
    SUPPLIERS_FIRST = No
    MERGED -> AttributeKeeper_6
AttributeKeeper_6
    KEEP_ATTRS = PCR_NBR,DIRECTION_CD,AVG_RUTTING_NBR,CRACKING_PCT_NBR,PCR_YEAR_NBR,PVMT_TYPE_CD,CTL_BEGIN_NBR,FAULTING_SAMPLE_IND,DOWN_RI_PVMT_TYPE_CD,AVG_FAULTING_NBR,NLF_ID,PSR_PCR_NBR,UP_RI_PVMT_TYPE_CD,PERP_YEAR_NBR,CRACKING_SAMPLE_IND,CTL_END_NBR,RUTTING_SAMPLE_IND
    -> AttributeRounder_6
AttributeRounder_6
    ROUND_TYPE = Nearest
    SRC_ATTRS = CTL_END_NBR CTL_BEGIN_NBR
    PLACES = 3
    -> BulkAttributeRenamer
BulkAttributeRenamer
    PATTERN_ACTION_DISP = ADDSUFFIX
    MODE_CHOICE = RENAME
    ATTRCHOICE = Selected Attributes
    ATTRLIST = CRACKING_PCT_NBR AVG_RUTTING_NBR AVG_FAULTING_NBR
    REPLACE_STR = _PCR
    -> Direction
Direction: Tester
    TEST_DESCRIPTION = ""
    TEST_CLAUSE = TEST @Value(DIRECTION_CD) = UP
    TEST_MODE = Automatic
    BOOL_OP = OR
    PASSED -> Junction_31
    FAILED -> Junction_21
Note: Sorter_2 : Input
Junction_31
    -> Junction_32
Note: AttributeRenamer_4 : Input
Junction_21
    -> Junction_22
dbo.RUTTING_HISTORY (reader MSSQL_ADO_1)
    attributes: RUTTING_HISTORY_ID identity, PERP_YEAR_NBR integer, PCR_YEAR_NBR integer, NLF_ID char(14), CTL_BEGIN_NBR numeric(7,3), CTL_END_NBR numeric(7,3), SEGMENT_LENGTH_NBR numeric(7,3), COLLECTION_DT varchar(20), DIRECTION_CD varchar(4), LEFT_RUTTING_NBR numeric(4,2), RIGHT_RUTTING_NBR numeric(4,2), AVG_RUTTING_NBR numeric(4,2), LATITUDE_BEGIN_NBR numeric(10,8), LONGITUDE_BEGIN_NBR numeric(10,8), LATITUDE_END_NBR numeric(10,8), LONGITUDE_END_NBR numeric(10,8), DATA_PROVIDER_TXT varchar(32)
    -> FeatureMerger_5 [REQUESTOR]
FeatureMerger_5
    PROCESS_DUPS = Yes
    REJECT_NULL_MISSING_KEYS = No
    CONNECT_Z_MODE = First Wins
    IGNORE_NULLS = No
    MERGE_TYPE = Attributes Only
    ATTR_CONFLICT_RES = Use Requestor
    GEOM_TYPE = Build Polygons
    JOIN_KEYS = @Value(NLF_ID) @Value(NLF_ID) AUTO
    ATTR_ACCUM_MODE = Merge Supplier
    SUPPLIERS_FIRST = No
    MERGED -> AttributeKeeper_2
AttributeKeeper_2
    KEEP_ATTRS = CTL_END_NBR,NLF_ID,RIGHT_RUTTING_NBR,DIRECTION_CD,LEFT_RUTTING_NBR,CTL_BEGIN_NBR,PCR_YEAR_NBR,PERP_YEAR_NBR,AVG_RUTTING_NBR
    -> AttributeRounder_4
AttributeRounder_4
    ROUND_TYPE = Nearest
    SRC_ATTRS = CTL_END_NBR CTL_BEGIN_NBR
    PLACES = 3
    -> Direction_4
Direction_4: Tester
    TEST_DESCRIPTION = ""
    TEST_CLAUSE = TEST @Value(DIRECTION_CD) = UP
    TEST_MODE = Automatic
    BOOL_OP = OR
    PASSED -> Junction_37
    FAILED -> Junction_27
Note: Sorter_2 : Input
Junction_37
    -> Junction_38
Note: AttributeKeeper_9 : Input
Junction_27
    -> Junction_28
dbo.CRACKING_HISTORY (reader MSSQL_ADO_1)
    attributes: CRACKING_HISTORY_ID identity, PERP_YEAR_NBR integer, PCR_YEAR_NBR integer, NLF_ID char(14), CTL_BEGIN_NBR numeric(7,3), CTL_END_NBR numeric(7,3), SEGMENT_LENGTH_NBR numeric(7,3), COLLECTION_DT varchar(20), DIRECTION_CD varchar(4), CRACKING_PCT_NBR numeric(5,2), CRACKING_LENGTH_NBR integer, LATITUDE_BEGIN_NBR numeric(10,8), LONGITUDE_BEGIN_NBR numeric(10,8), LATITUDE_END_NBR numeric(10,8), LONGITUDE_END_NBR numeric(10,8), DATA_PROVIDER_TXT varchar(32)
    -> FeatureMerger_6 [REQUESTOR]
FeatureMerger_6
    PROCESS_DUPS = Yes
    REJECT_NULL_MISSING_KEYS = No
    CONNECT_Z_MODE = First Wins
    IGNORE_NULLS = No
    MERGE_TYPE = Attributes Only
    ATTR_CONFLICT_RES = Use Requestor
    GEOM_TYPE = Build Polygons
    JOIN_KEYS = @Value(NLF_ID) @Value(NLF_ID) AUTO
    ATTR_ACCUM_MODE = Merge Supplier
    SUPPLIERS_FIRST = No
    MERGED -> AttributeKeeper
AttributeKeeper
    KEEP_ATTRS = CTL_END_NBR,CRACKING_PCT_NBR,NLF_ID,DIRECTION_CD,CRACKING_LENGTH_NBR,CTL_BEGIN_NBR,PCR_YEAR_NBR,PERP_YEAR_NBR
    -> AttributeRounder_8
AttributeRounder_8
    ROUND_TYPE = Nearest
    SRC_ATTRS = CTL_END_NBR CTL_BEGIN_NBR
    PLACES = 3
    -> Direction_5
Direction_5: Tester
    TEST_DESCRIPTION = ""
    TEST_CLAUSE = TEST @Value(DIRECTION_CD) = UP
    TEST_MODE = Automatic
    BOOL_OP = OR
    PASSED -> Junction_39
    FAILED -> Junction_29
Note: Sorter_2 : Input
Junction_39
    -> Junction_40
Note: AttributeKeeper_8 : Input
Junction_29
    -> Junction_30

Bookmark: SpatialOverlayer
Sorter_2
    SORT_PARM = NLF_ID ALPHA ASCENDING CTL_BEGIN_NBR NUMERIC ASCENDING CTL_END_NBR NUMERIC ASCENDING
    SORTED -> VertexCreator_2
Note: Replace geometry from measures
VertexCreator_2
    XVAL = @Value(CTL_BEGIN_NBR)
    MODE_NAME = Replace with Point
    YVAL = 0
    -> VertexCreator_3
VertexCreator_3
    XVAL = @Value(CTL_END_NBR)
    MODE_NAME = Add Point
    YVAL = 0
    -> LineOnLineOverlayer [LINE]
Note: Overlay measure geometry
LineOnLineOverlayer
    LOG_LEVEL = Full
    GROUP_BY = PERP_YEAR_NBR NLF_ID
    ATTRS_ACCUM_MODE = Merge Attributes
    GENERATE_LIST_DROP = NO
    DEAGGREGATE_INPUT = Yes
    SEPARATE_COLLINEAR_SEGMENTS = No
    LINE -> CoordinateExtractor
    <REJECTED> -> LineOnLineOverlayer__Rejected_
Note: Extract new measures
CoordinateExtractor
    MODE = Specify Coordinate
    X_ATTR = CTL_BEGIN_NBR
    IND = 0
    -> CoordinateExtractor_2
CoordinateExtractor_2
    MODE = Specify Coordinate
    X_ATTR = CTL_END_NBR
    IND = 1
    -> Sorter_5
Sorter_5
    SORT_PARM = NLF_ID ALPHA ASCENDING CTL_BEGIN_NBR NUMERIC ASCENDING CTL_END_NBR NUMERIC ASCENDING
    SORTED -> Sorter_5_SORTED_-__Tester_7
LineOnLineOverlayer__Rejected_: Inspector

Bookmark: SpatialOverlayer
Sorter_3
    SORT_PARM = NLF_ID ALPHA ASCENDING CTL_BEGIN_NBR NUMERIC ASCENDING CTL_END_NBR NUMERIC ASCENDING
    SORTED -> VertexCreator_4
Note: Replace geometry from measures
VertexCreator_4
    XVAL = @Value(CTL_BEGIN_NBR)
    MODE_NAME = Replace with Point
    YVAL = 0
    -> VertexCreator_5
VertexCreator_5
    XVAL = @Value(CTL_END_NBR)
    MODE_NAME = Add Point
    YVAL = 0
    -> LineOnLineOverlayer_2 [LINE]
Note: Overlay measure geometry
LineOnLineOverlayer_2
    LOG_LEVEL = Full
    GROUP_BY = PERP_YEAR_NBR NLF_ID
    ATTRS_ACCUM_MODE = Merge Attributes
    GENERATE_LIST_DROP = NO
    DEAGGREGATE_INPUT = Yes
    SEPARATE_COLLINEAR_SEGMENTS = No
    LINE -> CoordinateExtractor_3
    <REJECTED> -> LineOnLineOverlayer__Rejected__2
Note: Extract new measures
CoordinateExtractor_3
    MODE = Specify Coordinate
    X_ATTR = CTL_BEGIN_NBR
    IND = 0
    -> CoordinateExtractor_4
CoordinateExtractor_4
    MODE = Specify Coordinate
    X_ATTR = CTL_END_NBR
    IND = 1
    -> Sorter_6
Sorter_6
    SORT_PARM = NLF_ID ALPHA ASCENDING CTL_BEGIN_NBR NUMERIC ASCENDING CTL_END_NBR NUMERIC ASCENDING
    SORTED -> Sorter_5_SORTED_-__Tester_7
LineOnLineOverlayer__Rejected__2: Inspector

Bookmark: ONLY NHS
Tester_7
    TEST_DESCRIPTION = ""
    TEST_CLAUSE = TEST @Value(NHS_CD) ATTRIBUTE_HAS_VALUE ""
    TEST_MODE = Automatic
    BOOL_OP = OR
    PASSED -> Tester_5

Bookmark: RUTTING TEST
Tester_5
    TEST_DESCRIPTION = ""
    TEST_CLAUSE = TEST @Value(AVG_RUTTING_NBR) ATTRIBUTE_HAS_VALUE ""
    TEST_MODE = Automatic
    BOOL_OP = OR
    PASSED -> AttributeCreator_9
    FAILED -> Tester_6
AttributeCreator_9
    ATTR_TABLE = SET_TO RUTTING_PROVIDER = RUTTING
    -> AttributeCreator_3_OUTPUT_3
Tester_6
    TEST_DESCRIPTION = ""
    TEST_CLAUSE = TEST @Value(RUTTING_SAMPLE_IND) = Y
    TEST_MODE = Automatic
    BOOL_OP = OR
    PASSED -> AttributeCreator_10
    FAILED -> AttributeCreator_11
AttributeCreator_10
    ATTR_TABLE = SET_TO RUTTING_PROVIDER = PCR
    -> AttributeManager_8
AttributeManager_8
    ATTR_TABLE = SET_TO AVG_RUTTING_NBR = @Value(AVG_RUTTING_NBR_PCR)
    -> AttributeCreator_3_OUTPUT_3
AttributeCreator_11
    ATTR_TABLE = SET_TO RUTTING_PROVIDER = FME_NULL_VALUE
    -> AttributeCreator_3_OUTPUT_3

Bookmark: FAULTING TEST
AttributeCreator_3_OUTPUT_3: Junction
    -> Tester_3
Tester_3
    TEST_DESCRIPTION = ""
    TEST_CLAUSE = TEST @Value(AVG_FAULTING_NBR) ATTRIBUTE_HAS_VALUE ""
    TEST_MODE = Automatic
    BOOL_OP = OR
    PASSED -> AttributeCreator_6
    FAILED -> Tester_4
AttributeCreator_6
    ATTR_TABLE = SET_TO FAULTING_PROVIDER = FAULTING
    -> AttributeCreator_3_OUTPUT_2
Tester_4
    TEST_DESCRIPTION = ""
    TEST_CLAUSE = TEST @Value(FAULTING_SAMPLE_IND) = Y
    TEST_MODE = Automatic
    BOOL_OP = OR
    PASSED -> AttributeCreator_7
    FAILED -> AttributeCreator_8
AttributeCreator_7
    ATTR_TABLE = SET_TO FAULTING_PROVIDER = PCR
    -> AttributeManager_6
AttributeManager_6
    ATTR_TABLE = SET_TO AVG_FAULTING_NBR = @Value(AVG_FAULTING_NBR_PCR)
    -> AttributeCreator_3_OUTPUT_2
AttributeCreator_8
    ATTR_TABLE = SET_TO FAULTING_PROVIDER = FME_NULL_VALUE
    -> AttributeCreator_3_OUTPUT_2

Bookmark: CRACKING TEST
AttributeCreator_3_OUTPUT_2: Junction
    -> Tester
Tester
    TEST_DESCRIPTION = ""
    TEST_CLAUSE = TEST @Value(CRACKING_PCT_NBR) ATTRIBUTE_HAS_VALUE ""
    TEST_MODE = Automatic
    BOOL_OP = OR
    PASSED -> AttributeCreator_3
    FAILED -> Tester_2
AttributeCreator_3
    ATTR_TABLE = SET_TO CRACKING_PROVIDER = CRACKING
    -> AttributeCreator_3_OUTPUT
Tester_2
    TEST_DESCRIPTION = ""
    TEST_CLAUSE = TEST @Value(CRACKING_SAMPLE_IND) = Y
    TEST_MODE = Automatic
    BOOL_OP = OR
    PASSED -> AttributeCreator_4
    FAILED -> AttributeCreator_5
AttributeCreator_4
    ATTR_TABLE = SET_TO CRACKING_PROVIDER = PCR
    -> AttributeManager_3
AttributeManager_3
    ATTR_TABLE = SET_TO CRACKING_PCT_NBR = @Value(CRACKING_PCT_NBR_PCR)
    -> AttributeCreator_3_OUTPUT
AttributeCreator_5
    ATTR_TABLE = SET_TO CRACKING_PROVIDER = FME_NULL_VALUE
    -> AttributeCreator_3_OUTPUT

Bookmark: PSR CREATION
AttributeCreator_3_OUTPUT: Junction
    -> Tester_8
Tester_8
    TEST_DESCRIPTION = ""
    TEST_CLAUSE = TEST @Value(RIDE_NBR) ATTRIBUTE_HAS_VALUE ""
    TEST_MODE = Automatic
    BOOL_OP = OR
    PASSED -> AttributeManager_5
    FAILED -> Tester_9
AttributeManager_5
    ATTR_TABLE:
      SET_TO PSR_PROVIDER = RIDE
      SET_TO PSR_NBR = @Value(RIDE_NBR)
    -> AttributeCreator_3_OUTPUT_4
Tester_9
    TEST_DESCRIPTION = ""
    TEST_CLAUSE = TEST @Value(PSR_PCR_NBR) ATTRIBUTE_HAS_VALUE ""
    TEST_MODE = Automatic
    BOOL_OP = OR
    PASSED -> AttributeManager_2
    FAILED -> AttributeCreator_14
AttributeManager_2
    ATTR_TABLE:
      SET_TO PSR_PROVIDER = PCR
      SET_TO PSR_NBR = @Value(PSR_PCR_NBR)
    -> AttributeCreator_3_OUTPUT_4
AttributeCreator_14
    ATTR_TABLE = SET_TO PSR_PROVIDER = FME_NULL_VALUE
    -> AttributeCreator_3_OUTPUT_4
AttributeCreator_3_OUTPUT_4: Junction
    -> AttributeCreator

Bookmark: Length Calculation
AttributeCreator
    ATTR_TABLE:
      SET_TO SEGMENT_LENGTH_NBR = @Evaluate(@abs(@Value(CTL_END_NBR)-@Value(CTL_BEGIN_NBR)))
      SET_TO AVG_IRI_NBR = @Evaluate((@Value(LIRI_NBR)+@Value(RIRI_NBR))/2)
    -> AttributeRemover

Bookmark: SET PCR YEAR
AttributeRemover
    REMOVE_ATTRS = PCR_YEAR_NBR
    -> AttributeManager
AttributeManager
    ATTR_TABLE = SET_TO PCR_YEAR_NBR = @Evaluate(@Value(PERP_YEAR_NBR)+1)
    -> AttributeRenamer
